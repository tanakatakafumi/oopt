module packet-transport {
    yang-version 1;
    namespace "http://example.com";
    prefix "pkt-transport";

    import openconfig-terminal-device { prefix oc-opt-term; }
    import openconfig-platform-port { prefix oc-port; }
    import openconfig-interfaces { prefix oc-if; }

    typedef frequency-grid-type {
        type enumeration {
            enum GRID_100GHZ {
            }
            enum GRID_50GHZ {
            }
            enum GRID_33GHZ {
            }
            enum GRID_25GHZ {
            }
        }
    }

    typedef optical-module-status-type {
        type enumeration {
            enum STATE_DOWN {
            }
            enum STATE_BOOTING_TOP_HALF {
            }
            enum STATE_WAITING_RX_SIGNAL {
            }
            enum STATE_BOOTING_BOTTOM_HALF {
            }
            enum STATE_TESTING {
            }
            enum STATE_READY {
            }
            enum STATE_RESETTING {
            }
        }
    }

    typedef optical-modulation-type {
        type enumeration {
            enum DP_QPSK {
            }
            enum DP_16QAM {
            }
            enum DP_QPSK_INTEROP {
            }
        }
    }

    grouping port-config {
        leaf name {
            type string;
        }

        leaf description {
            type string;
        }
    }

    grouping port-state {
    }

    grouping optical-module-module-config {
        leaf name {
            description
                "name of the optical module to connect this port";
            type string;
        }
        leaf channel {
            description
                "channel of the optical module to connect this port";
            type string;
        }
    }

    grouping optical-module-connection-config {

        leaf id {
            description
                "id for traffic aggregated on single optical module.
                Current implementation uses VLAN for traffic aggregation.
                This id is directly used as VLAN ID.
                client interfaces act as an access port, line interfaces act as an trunk port.";
            type uint32;
        }
    }

    grouping optical-module-connection-top {
        container optical-module-connection {

            container optical-module {
                container config {
                    uses optical-module-module-config;
                }
                container state {
                    uses optical-module-module-config;
                    config false;
                }
            }

            container config {
                uses optical-module-connection-config;
            }

            container state {
                config false;
                uses optical-module-connection-config;
            }
        }
    }

    grouping optical-module-frequency-config {
        leaf grid {
            type frequency-grid-type;
        }
        leaf channel {
            type uint8;
        }
    }

    grouping optical-module-config {
        leaf name {
            type string;
        }

        leaf description {
            type string;
        }

        leaf enabled {
            type boolean;
        }

        leaf modulation-type {
            type optical-modulation-type;
        }

        leaf ber-interval {
            type uint32;
        }

        leaf prbs {
            type boolean;
        }

        leaf losi {
            type boolean;
        }
    }

    grouping optical-module-state-rms {
        leaf xi {
            type uint16;
        }
        leaf xq {
            type uint16;
        }
        leaf yi {
            type uint16;
        }
        leaf yq {
            type uint16;
        }

    }

    grouping optical-module-state {

        leaf sync-error {
            type boolean;
        }

        leaf operation-status {
            type optical-module-status-type;
        }

        list channel-stats {
            key "name";

            leaf name {
                type string;
            }

            leaf sd-fec-ber {
                type string;
            }

            leaf hd-fec-ber {
                type string;
            }

            leaf post-fec-ber {
                type string;
            }
        }

    }

    container packet-transponder {

        container ports {
            list port {
                key "name";

                description "port represents ethernet front panel ports of packet-transponder.
                    This doesn't include optical module ports.
                    We can configure breakout and speed configuration here.";

                leaf name {
                    type leafref {
                        path "../config/name";
                    }
                }

                container config {
                    uses port-config;
                }

                container state {
                    config false;
                    uses port-config;
                    uses port-state;
                }

                uses oc-port:port-breakout-top;
            }
        }

        container interfaces {
            list interface {
                key "name";

                description "interface represents ethernet interfaces.
                    when a port is configured to break out into 4, 4 interfaces will be created.
                    We can configure the connection between interface and optical module here";

                leaf name {
                    type leafref {
                        path "../config/name";
                    }
                }

                container config {
                    uses oc-if:interface-phys-config;
                }

                container state {
                    uses oc-if:interface-phys-config;
                    uses oc-if:interface-common-state;
                    uses oc-if:interface-counters-state;
                }

                uses optical-module-connection-top;

            }
        }

        container optical-modules {
            list optical-module {
                key "name";

                leaf name {
                    type leafref {
                        path "../config/name";
                    }
                }

                container optical-module-frequency {
                    container config {
                        uses optical-module-frequency-config;
                    }
                    container state {
                        config false;
                        uses optical-module-frequency-config;
                    }
                }

                container optical-module-rms {
                    container state {
                        config false;
                        uses optical-module-state-rms;
                    }
                }

                container config {
                    uses optical-module-config;
                }

                container state {
                    config false;
                    uses optical-module-config;
                    uses optical-module-state;
                }

            }
        }
    }

    deviation "/pkt-transport:packet-transponder/pkt-transport:ports/pkt-transport:port/" +
        "pkt-transport:breakout-mode/pkt-transport:config/pkt-transport:num-channels" {
            deviate replace {
                type uint8 {
                    range "1|4";
                }
            }
    }
}
